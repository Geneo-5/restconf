module restconf-test {
    namespace "urn:restconf:test";
    prefix rt;

    import ietf-inet-types {
        prefix inet;
    }
    import ietf-yang-types {
        prefix yang;
    }

    revision 2026-07-08 {
        description
            "RESTCONF Qualification Test Module.
             Contains all YANG constructs required for RFC8040, RFC8527, and RFC7950 compliance testing.
             This module MUST be loaded for qualification tests to run properly.
             
             Usage: Tests must verify that this module is loaded and accessible via RESTCONF
             before executing test cases that require specific YANG features.";
    }

    // ========================================================================
    // IDENTITIES (RFC7950) - For identityref testing (TC-7-026)
    // ========================================================================
    identity sensor-type {
        description "Base identity for sensor types";
    }
    identity temperature-sensor {
        base sensor-type;
        description "Temperature sensor";
    }
    identity humidity-sensor {
        base sensor-type;
        description "Humidity sensor";
    }
    identity pressure-sensor {
        base sensor-type;
        description "Pressure sensor";
    }

    // ========================================================================
    // TYPEDDEFS (RFC7950) - For type constraint testing
    // ========================================================================
    typedef percentage {
        type uint8 {
            range "0..100";
        }
    }

    typedef device-name {
        type string {
            pattern '[a-zA-Z][a-zA-Z0-9-]{0,19}';
        }
    }

    typedef serial-number {
        type string {
            length "8..20";
        }
    }

    typedef temperature-celsius {
        type int16 {
            range "-273..1000";
        }
        units "degrees Celsius";
    }

    // ========================================================================
    // BASIC CONTAINERS (RFC8040 §3.3, RFC7950)
    // ========================================================================
    container system {
        description "Root container for system configuration and state";

        container config {
            presence "System configuration is present";
            description "Configuration container with presence";
            
            leaf system-name {
                type device-name;
                description "System name";
            }
        }

        container state {
            config false;
            description "Operational state container";
            
            leaf system-status {
                type string;
                config false;
                description "Current system status";
            }
        }
    }

    // ========================================================================
    // MANDATORY, DEFAULT, READ-ONLY (RFC7950 §7.6)
    // TC-3-039, TC-7-014: mandatory
    // TC-7-023, TC-7-024: boolean
    // TC-3-017, TC-3-021, TC-3-031: read-only
    // ========================================================================
    container basic-data {
        description "Test container for basic data types and constraints";

        // Mandatory leaf (TC-3-039, TC-7-014) - mandatory commenté pour installation sysrepo
        leaf device-id {
            type device-name;
            mandatory true;
            description "MANDATORY: Device identifier must be present";
        }

        // Leaf with default (TC-7-023, TC-7-024)
        leaf timeout {
            type uint16;
            default 30;
            units "seconds";
            description "Leaf with default value";
        }

        // Read-only leaf (TC-3-017, TC-3-021, TC-3-031)
        leaf uptime {
            type uint32;
            config false;
            units "seconds";
            description "READ-ONLY: System uptime";
        }

        // Boolean leaf (TC-7-023)
        leaf enabled {
            type boolean;
            default true;
            description "Boolean field for type testing";
        }
    }

    // ========================================================================
    // LISTS (RFC7950 §7.7) - For TC-3-005, TC-3-006, TC-3-011, TC-3-029, etc.
    // ========================================================================
    container interfaces {
        description "Container for list testing (RFC8040 §4.2)";

        // Simple list with key (TC-3-005, TC-3-006, TC-3-011, TC-3-014, TC-3-015)
        list interface {
            key "name";
            description "Network interface list - for GET/POST/PUT/PATCH/DELETE testing";

            leaf name {
                type device-name;
                description "Interface name - used as key";
            }

            leaf description {
                type string;
                description "Interface description";
            }

            leaf enabled {
                type boolean;
                default true;
                description "Interface enabled status";
            }

            leaf mtu {
                type uint16 {
                    range "64..9192";
                }
                description "Maximum Transmission Unit";
            }

            // Unique constraint (TC-7-033)
            unique "name";
        }

        // List with min/max elements (TC-7-015, TC-7-016)
        list vlan {
            key "vlan-id";
            // min-elements 1;  // Commenté pour installation sysrepo
            max-elements 4094;
            description "VLAN configuration - for min/max elements testing";

            leaf vlan-id {
                type uint16 {
                    range "1..4094";
                }
                description "VLAN ID";
            }

            leaf name {
                type string;
                description "VLAN name";
            }
        }

        // Ordered list (TC-4-031 to TC-4-034, TC-7-034, TC-7-035)
        list ordered-queue {
            key "position";
            ordered-by user;
            description "Ordered list for insert parameter testing";

            leaf position {
                type uint8;
                description "Position in queue";
            }

            leaf item {
                type string;
                description "Queue item name";
            }
        }

        // List with presence conditional on another leaf (WHEN constraint)
        container advanced-features {
            leaf enable-advanced {
                type boolean;
                default false;
                description "Enable advanced features";
            }

            list advanced-interface {
                key "name";
                when "../enable-advanced = 'true'";
                description "Only present when advanced features are enabled - for WHEN constraint testing (TC-3-049, TC-7-032)";

                leaf name {
                    type device-name;
                }

                leaf advanced-setting {
                    type uint8;
                    description "Advanced setting value";
                }
            }
        }
    }

    // ========================================================================
    // LEAF-LISTS (RFC7950 §7.8) - For TC-3-008
    // ========================================================================
    container access-control {
        description "Container for leaf-list testing";

        // Simple leaf-list (TC-3-008)
        leaf-list allowed-ips {
            type inet:ipv4-address;
            description "List of allowed IP addresses - for leaf-list testing";
        }

        // Leaf-list with constraints (TC-7-015, TC-7-016)
        leaf-list allowed-macs {
            type string {
                pattern '[0-9a-fA-F]{2}(:[0-9a-fA-F]{2}){5}';
            }
            // min-elements 1;  // Commenté pour installation sysrepo
            max-elements 10;
            description "List of allowed MAC addresses - for constrained leaf-list testing";
        }

        // Leaf-list for duplicate testing (TC-7-040)
        leaf-list tags {
            type string;
            description "List of tags - for duplicate key testing";
        }
    }

    // ========================================================================
    // ANYDATA / ANYXML (RFC7950 §7.10, §7.11) - For TC-3-009, TC-3-010, TC-7-043-045
    // NOTE: Commenté car libyang 5.8.6 a des problèmes avec anydata/anyxml
    // ========================================================================
    // container custom-data {
    //     description "Container for anydata/anyxml testing";
    //
    //     anydata vendor-specific {
    //         description "Anydata field for vendor extensions - for TC-3-009, TC-7-043";
    //     }
    //
    //     anyxml legacy-config {
    //         description "Anyxml field for legacy configuration - for TC-3-010, TC-7-044, TC-7-045";
    //     }
    // }

    // ========================================================================
    // ADVANCED TYPES (RFC7950 §9) - For TC-7-018, TC-7-020-022, TC-7-026-030
    // ========================================================================
    container advanced-types {
        description "Container for advanced type testing";

        // Union type (TC-7-029)
        leaf mixed-value {
            type union {
                type uint8;
                type string;
                type inet:ipv4-address;
            }
            description "Union of multiple types - for TC-7-029";
        }

        // Bits type (TC-7-021)
        leaf feature-flags {
            type bits {
                bit logging {
                    position 0;
                    description "Enable logging";
                }
                bit monitoring {
                    position 1;
                    description "Enable monitoring";
                }
                bit debugging {
                    position 2;
                    description "Enable debugging";
                }
                bit security {
                    position 3;
                    description "Enable security features";
                }
            }
            description "Feature flags using bits type - for TC-7-021";
        }

        // Decimal64 (TC-7-022)
        leaf precision-value {
            type decimal64 {
                fraction-digits 4;
                range "0..10000.0000";
            }
            description "Decimal64 value with precision - for TC-7-022";
        }

        // Binary (TC-7-030)
        leaf certificate {
            type binary;
            description "Binary certificate data - for TC-7-030";
        }

        // Identityref (TC-7-026)
        leaf sensor-type-ref {
            type identityref {
                base sensor-type;
            }
            default temperature-sensor;
            description "Reference to sensor type identity - for TC-7-026";
        }

        // Leafref (TC-3-048, TC-7-027)
        leaf default-interface {
            type leafref {
                path "/rt:interfaces/rt:interface/rt:name";
            }
            description "Reference to an existing interface - for TC-3-048, TC-7-027";
        }
    }

    // ========================================================================
    // CONSTRAINTS (RFC7950 §7.5.3) - For TC-3-043, TC-3-049-050, TC-7-017-018, TC-7-031-033
    // ========================================================================
    container constraints {
        description "Container for logical constraint testing";

        // Range constraint (TC-3-043, TC-7-018)
        container range-test {
            description "Container for range constraint testing";

            leaf percentage-value {
                type percentage;
                description "Value with percentage range (0-100) - for TC-3-043, TC-7-018";
            }

            leaf temperature {
                type temperature-celsius;
                description "Temperature with range constraint";
            }
        }

        // MUST constraint (TC-3-050, TC-7-031)
        container must-test {
            description "Container with MUST constraint - for TC-3-050, TC-7-031";

            leaf start-time {
                type uint32;
                description "Start time";
            }

            leaf end-time {
                type uint32;
                description "End time";
            }

            // must "start-time < end-time" {
            //     error-message "Start time must be less than end time";
            //     error-app-tag "invalid-range";
            // } // Commenté pour installation sysrepo
        }

        // WHEN constraint (TC-3-049, TC-7-032) - also used in interfaces/advanced-features
        container when-test {
            description "Container for WHEN constraint testing";

            leaf enable-optional {
                type boolean;
                default false;
                description "Enable optional features";
            }

            container optional-config {
                when "../enable-optional = 'true'";
                description "Configuration only valid when enabled - for TC-3-049, TC-7-032";

                leaf optional-value {
                    type uint8;
                    description "Optional value";
                }
            }
        }

        // Unique constraint (TC-7-033) - also used in interfaces/interface
        container unique-test {
            description "Container for UNIQUE constraint testing";

            list items {
                key "id";
                unique "name priority";
                description "List with unique constraint on multiple fields";

                leaf id {
                    type uint8;
                }

                leaf name {
                    type string;
                }

                leaf priority {
                    type uint8;
                }
            }
        }

        // Length constraint (TC-7-019)
        leaf password {
            type string {
                length "8..64";
            }
            description "Password with length constraint - for TC-7-019";
        }

        // Pattern constraint (TC-7-017)
        leaf email {
            type string {
                pattern '[a-zA-Z0-9._%+-]+@[a-zA-Z0-9.-]+\.[a-zA-Z]{2,}';
            }
            description "Email address with pattern constraint - for TC-7-017";
        }

        // Enum constraint (TC-7-020, TC-3-045)
        leaf operation-mode {
            type enumeration {
                enum "normal" {
                    value 1;
                    description "Normal operation mode";
                }
                enum "maintenance" {
                    value 2;
                    description "Maintenance mode";
                }
                enum "emergency" {
                    value 3;
                    description "Emergency mode";
                }
            }
            description "Enumeration type - for TC-7-020, TC-3-045";
        }

        // Min/Max elements in list (TC-7-015, TC-7-016)
        // Already covered in interfaces/vlan
    }

    // ========================================================================
    // RPC (RFC7950 §7.15, RFC8040 §5) - For TC-5-001-014
    // ========================================================================
    
    // RPC discovery - root level
    // Note: RPCs are exposed under /restconf/operations per RFC8040

    // RPC without parameters (TC-5-004)
    rpc get-system-status {
        description "RPC without input parameters - for TC-5-004";

        output {
            leaf status {
                type string;
                description "System status";
            }
            leaf timestamp {
                type yang:date-and-time;
                description "When status was retrieved";
            }
        }
    }

    // RPC with parameters (TC-5-005)
    rpc configure-device {
        description "RPC with input parameters - for TC-5-005";

        input {
            leaf device-name {
                type device-name;
                mandatory true;
                description "Device name - mandatory parameter";
            }

            leaf enable {
                type boolean;
                default true;
                description "Enable device";
            }

            leaf settings {
                type string;
                description "Device settings";
            }
        }

        output {
            leaf result {
                type string;
                description "Operation result";
            }
            leaf device-id {
                type uint32;
                description "Assigned device ID";
            }
        }
    }

    // RPC with mandatory parameter (TC-5-006)
    rpc create-resource {
        description "RPC with mandatory parameter - for TC-5-006";

        input {
            leaf name {
                type string;
                mandatory true;
                description "MANDATORY: Resource name must be provided";
            }
        }

        output {
            leaf id {
                type uint32;
                description "Created resource ID";
            }
        }
    }

    // RPC with enum parameter (TC-5-007, TC-7-020)
    rpc set-operation-mode {
        description "RPC with enumeration parameter - for TC-5-007";

        input {
            leaf mode {
                type enumeration {
                    enum "normal" {
                        value 1;
                        description "Normal operation mode";
                    }
                    enum "maintenance" {
                        value 2;
                        description "Maintenance mode";
                    }
                    enum "emergency" {
                        value 3;
                        description "Emergency mode";
                    }
                }
                mandatory true;
                description "Operation mode - enumeration type";
            }
        }

        output {
            leaf previous-mode {
                type enumeration {
                    enum "normal";
                    enum "maintenance";
                    enum "emergency";
                }
                description "Previous operation mode";
            }
        }
    }

    // RPC with type validation (TC-5-007)
    rpc process-data {
        description "RPC for type validation testing - for TC-5-007";

        input {
            leaf uint-value {
                type uint8 {
                    range "0..100";
                }
                description "Value with range constraint";
            }
            leaf enum-value {
                type enumeration {
                    enum "option1";
                    enum "option2";
                }
                description "Enumeration value";
            }
        }

        output {
            leaf processed {
                type boolean;
                description "Whether data was processed successfully";
            }
        }
    }

    // RPC with no output (TC-5-011)
    rpc trigger-event {
        description "RPC with no output - for TC-5-011";

        input {
            leaf event-type {
                type string;
                mandatory true;
            }
        }
    }

    // ========================================================================
    // ACTIONS (YANG 1.1, RFC7950) - For TC-5-015-019
    // NOTE: Commenté car libyang 5.8.6 a des problèmes avec les actions YANG 1.1
    // ========================================================================
    //
    // container device-management {
    //     description "Container for action testing";
    //
    //     // Action without parameters (TC-5-015, TC-5-016)
    //     action reset {
    //         description "Reset action without parameters - for TC-5-015";
    //         output {
    //             leaf status {
    //                 type string;
    //                 description "Reset operation status";
    //             }
    //         }
    //     }
    //
    //     // Action with parameters (TC-5-015, TC-5-016, TC-5-018)
    //     action test-connection {
    //         description "Test connection action with parameters - for TC-5-015, TC-5-016";
    //         input {
    //             leaf target {
    //                 type inet:host;
    //                 mandatory true;
    //                 description "Target host to test";
    //             }
    //             leaf timeout {
    //                 type uint16;
    //                 default 5;
    //                 units "seconds";
    //                 description "Connection timeout";
    //             }
    //         }
    //         output {
    //             leaf success {
    //                 type boolean;
    //                 description "Connection test result";
    //             }
    //             leaf latency {
    //                 type uint32;
    //                 units "milliseconds";
    //                 description "Connection latency";
    //             }
    //         }
    //     }
    //
    //     // Action on resource (TC-5-017)
    //     list managed-device {
    //         key "device-id";
    //         description "List of managed devices for action testing";
    //
    //         leaf device-id {
    //             type uint32;
    //         }
    //
    //         leaf device-name {
    //             type string;
    //         }
    //
    //         action reboot {
    //             description "Reboot action on specific device - for TC-5-017";
    //             input {
    //                 leaf force {
    //                     type boolean;
    //                     default false;
    //                 }
    //             }
    //             output {
    //                 leaf status {
    //                     type string;
    //                 }
    //                 leaf reboot-time {
    //                     type uint32;
    //                     units "seconds";
    //                 }
    //             }
    //         }
    //     }
    // }

    // ========================================================================
    // NOTIFICATIONS (RFC7950 §7.16, RFC8040 §6) - For TC-5-020-040
    // ========================================================================
    
    // Simple notification (TC-5-020, TC-5-021)
    notification system-startup {
        description "System startup notification - for TC-5-020, TC-5-021";
        leaf timestamp {
            type yang:date-and-time;
            description "When system started";
        }
        leaf message {
            type string;
            description "Startup message";
        }
    }

    // Notification with structured data (TC-5-026)
    notification threshold-exceeded {
        description "Notification with structured data - for TC-5-026";
        leaf sensor-name {
            type device-name;
            description "Name of the sensor that exceeded threshold";
        }
        leaf current-value {
            type decimal64 {
                fraction-digits 2;
            }
            description "Current measured value";
        }
        leaf threshold {
            type decimal64 {
                fraction-digits 2;
            }
            description "Threshold value that was exceeded";
        }
        leaf timestamp {
            type yang:date-and-time;
            description "When threshold was exceeded";
        }
        leaf severity {
            type enumeration {
                enum "warning";
                enum "critical";
            }
            description "Severity of the threshold breach";
        }
    }

    // Notification for stream testing (TC-5-022-025, TC-5-027-030)
    notification event-notification {
        description "Generic event notification for stream testing - for TC-5-022-030";
        leaf event-type {
            type string;
            mandatory true;
            description "Type of event";
        }
        leaf severity {
            type enumeration {
                enum info;
                enum warning;
                enum error;
                enum critical;
            }
            description "Event severity";
        }
        leaf source {
            type string;
            description "Event source";
        }
        leaf description {
            type string;
            description "Event description";
        }
        leaf timestamp {
            type yang:date-and-time;
            description "Event timestamp";
        }
    }

    // Notification for error conditions (TC-5-012, TC-5-013)
    notification system-alert {
        description "System alert notification";
        leaf alert-type {
            type string;
        }
        leaf message {
            type string;
        }
        leaf code {
            type uint32;
        }
    }
}
